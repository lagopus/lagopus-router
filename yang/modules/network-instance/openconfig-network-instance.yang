module openconfig-network-instance {

  yang-version "1";

  // namespace
  namespace "http://lagopus.org/yang/network-instance";

  prefix "oc-netinst";

  import ietf-yang-types { prefix "yang"; }
  import openconfig-network-instance-types { prefix "oc-ni-types"; }
  import openconfig-network-instance-l3 { prefix "oc-ni-l3"; }
  import openconfig-vlan { prefix "oc-vlan"; }
  import lagopus-policy-based-routing {prefix "lago-pbr"; }

  // include submodules
  include openconfig-network-instance-l2;

  // meta
  organization "OpenConfig working group";

  contact
    "OpenConfig working group
    www.openconfig.net";

  description
    "An OpenConfig description of a network-instance. This may be
    a Layer 3 forwarding construct such as a virtual routing and
    forwarding (VRF) instance, or a Layer 2 instance such as a
    virtual switch instance (VSI). Mixed Layer 2 and Layer 3
    instances are also supported.";

  revision "2017-12-11" {
    description
      "Refactoring for beta version";
    reference "0.8.0-lagopus-0.2.0";
  }

  revision "2017-07-26" {
    description
      "Initial revision for lagopus router.";
    reference "0.8.0-lagopus-0.1.0";
  }

  revision "2017-02-28" {
    description
      "Add OSPFv2 to network instance";
    reference "0.8.0";
  }

  revision "2017-01-26" {
    description
      "Add policy forwarding to network instance";
    reference "0.7.0";
  }

  revision "2017-01-13" {
    description
      "Add AFT to the network instance";
    reference "0.6.0";
  }

  revision "2016-12-15" {
    description
      "Add segment routing to network instance";
    reference "0.5.0";
  }

  revision "2016-11-10" {
    description
      "Add IS-IS to OpenConfig network instance";
    reference "0.4.1";
  }

  revision "2016-10-12" {
    description
      "Update table connections";
    reference "0.4.0";
  }

  revision "2016-09-28" {
    description
      "Change L2 instance to submodule; add MAC table";
    reference "0.3.0";
  }

  revision "2016-08-11" {
    description
      "Resolve repeated container names in routing protocols";
    reference "0.2.3";
  }

  revision "2016-07-08" {
    description
      "Updated with refactored routing protocol models";
    reference "0.2.1";
  }

  revision "2016-03-29" {
    description
      "Initial revision";
    reference "0.2.0";
  }

  revision "2015-10-18" {
    description
      "Initial revision";
    reference "0.1.0";
  }


  grouping network-instance-top {
    description
      "Top-level grouping containing a list of network instances.";

    container network-instances {
      description
        "The L2, L3, or L2+L3 forwarding instances that are
        configured on the local system";

      list network-instance {
        key "name";

        description
          "Network instances configured on the local system";

        leaf name {
	  type string;
          description
            "An operator-assigned unique name for the forwarding
            instance";
        }

        uses l2ni-instance {
	  description
	    "Layer 2 configuration parameters included when
            a network instance is a Layer 2 instance or a
            combined L2L3 instance";
        }

        container config {
          description
            "Configuration parameters relating to a network
            instance";
          uses network-instance-config;
          uses network-instance-type-dependent-config;
        }

        container interfaces {
          description
            "The interfaces that are associated with this network
            instance";

          list interface {
            key "name";

            description
              "An interface associated with the network instance";

	    leaf name {
	      type string;
	      description "";
	    }

	    list subinterface {
	      key "index";

	      description
		"";
	      leaf index {
		type uint32;
		description "";
	      }
	    }
          }
        }
	uses lago-pbr:pbr-entries-top;
        uses oc-vlan:vlan-top;
      }
    }
  }

  grouping network-instance-type-dependent-config {
    description
      "Type dependent network instance configuration";

    uses oc-ni-l3:l3ni-instance-common-config {
      description
        "Layer 3 VRF configuration parameters included when a
        network instance is a L3VRF or combined L2L3 instance";
    }

    uses l2ni-instance-common-config {
      description
        "Layer 2 configuration parameters included when
        a network instance is a Layer 2 instance or a
        combined L2L3 instance";
    }
  }

  grouping network-instance-config {
    description
      "Configuration parameters relating to a top-level network
      instance";

    leaf type {
      type oc-ni-types:NETWORK_INSTANCE_TYPE;
      description
        "The type of network instance. The value of this leaf
        indicates the type of forwarding entries that should be
        supported by this network instance";
    }

    leaf enabled {
      type boolean;
      mandatory true;
      description
        "Whether the network instance should be configured to be
        active on the network element";
    }

    leaf description {
      type string;
      description
        "A free-form string to be used by the network operator to
        describe the function of this network instance";
    }

    leaf router-id {
      type yang:dotted-quad;
      description
        "A identifier for the local network instance - typically
        used within associated routing protocols or signalling
        routing information in another network instance";
    }

    leaf route-distinguisher {
      type oc-ni-types:route-distinguisher;
      description
        "The route distinguisher that should be used for the local
        VRF or VSI instance when it is signalled via BGP.";
    }
  }
}
